'''''''''''''''''''''''''''''''''''''''''''''''''''''''''''''''''''''''''''''
' ViewCapturePolyhedra.rvb -- May 2014
' If this code works, it was written by Dale Fugier.
' If not, I don't know who wrote it.
' Works with Rhino 5.
' Requries RhinoPolyhedra - http://www.food4rhino.com/project/rhinopolyhedra
'''''''''''''''''''''''''''''''''''''''''''''''''''''''''''''''''''''''''''''
Option Explicit

'''''''''''''''''''''''''''''''''''''''''''''''''''''''''''''''''''''''''''''''
' Main Subroutine
' View captures all polyhedra to an output folder of your choosing
'''''''''''''''''''''''''''''''''''''''''''''''''''''''''''''''''''''''''''''''
Sub ViewCapturePolyhedra
	
	' Local variables
	Dim strPlugIn, strFolder, strPath
	Dim arrDisplayModes, strDisplayMode, i
	Dim arrCommands, strCommand
	
	strPlugIn = "Rhino Polyhedra"
	
	' Make sure were are running Rhino 5       
	If (Rhino.ExeVersion < 5) Then
		Call Rhino.Print("This script requires Rhino 5.0 for greater.")
		Exit Sub
	End If	
	
	' Make sure RhinoPolyhedra is registered
	If Not Rhino.IsPlugIn(strPlugIn) Then
		Call Rhino.Print(strPlugIn & " plug-in not registered.")
	End If
	
	' Disable developer errors and warnings
	DisableErrorCheck
	
	' Pick an output folder
	strFolder = Rhino.BrowseForFolder(Rhino.WorkingFolder, "Select Output Folder:", strPlugIn)
	If IsNull(strFolder) Then Exit Sub
	
	' Pick a display mode
	arrDisplayModes = Rhino.ViewDisplayModes(True)
	For i = 0 To UBound(arrDisplayModes)
		arrDisplayModes(i) = Replace(arrDisplayModes(i), " ", "", 1, -1)
	Next
	strDisplayMode = Rhino.ListBox(arrDisplayModes, "Display Mode to Capture:", strPlugIn)
	If IsNull(strDisplayMode) Then Exit Sub
	
	' Get the Polyhedra commands
	arrCommands = GetPolyhedraCommands

	' Get rid of anything alredy in the model
	Call Rhino.Command("_SelAll", False)
	Call Rhino.Command("_Delete", False)
	
	' Set up the viewport to capture
	Call Rhino.Command("_4View", False)
	Call Rhino.CurrentView("Perspective")
	Call Rhino.Command("_SetView _World _Perspective", False)
	Call Rhino.Command("_SetDisplayMode _Viewport=_Active _Mode=_" & strDisplayMode, False)
		
	' Process each command
	For Each strCommand In arrCommands
		
		' Run the command
		Call Rhino.Command(strCommand & " 0 _Output=_Faces 1.0", False)
		
		' Zoom extents
		Call Rhino.Command("_Zoom Extents", False)

		' If rendering, create some materials
		If strDisplayMode = "Rendered" Then
			Call Rhino.Command("_SelAll", 0)
			Call Rhino.Command("_SynchronizeRenderColors", False)
			Call Rhino.Command("_SelNone", False)
		End If

		' Capture the view
		strPath = GetFilePath(strFolder, strCommand)
		Call Rhino.Command("_-ViewCaptureToFile " & strPath & " _DrawGrid=_No _DrawWorldAxes=_No _DrawCPlaneAxes=_No _Enter", False)

		' Clear the scene
		Call Rhino.Command("_SelAll", False)
		Call Rhino.Command("_Delete", False)

		' Just to keep memory tidy, clean out unused stuff
		Call Rhino.Command("_ClearUndo", False)
		Call Rhino.Command("_Purge _Enter", False)
		
		' Force Rhino to flush its message queue.
		' In doing this, we might be able to cancel the script by
		' pressing <Esc>...
		Call Rhino.Sleep(0)
	Next

End Sub

'''''''''''''''''''''''''''''''''''''''''''''''''''''''''''''''''''''''''''''''
' Builds a file path given a folder and a command name
'''''''''''''''''''''''''''''''''''''''''''''''''''''''''''''''''''''''''''''''
Function GetFilePath(strFolder, strCommand)
	' Surround file path in double quotes (in case it contains spaces)
	GetFilePath = Chr(34) & strFolder & "\" & strCommand & ".png" & Chr(34)
End Function

'''''''''''''''''''''''''''''''''''''''''''''''''''''''''''''''''''''''''''''''
' Disable developer errors and warnings you get if
' the Rhino C++ SDK is installed.
'''''''''''''''''''''''''''''''''''''''''''''''''''''''''''''''''''''''''''''''
Function DisableErrorCheck
	Call Rhino.Command("_TestErrorCheck _ErrorMessages=_Off _Enter", False)	
End Function

'''''''''''''''''''''''''''''''''''''''''''''''''''''''''''''''''''''''''''''''
' Returns a objList of RhinoPolyhedra commands
'''''''''''''''''''''''''''''''''''''''''''''''''''''''''''''''''''''''''''''''
Function GetPolyhedraCommands
	Dim objList
	Set objList = CreateObject("System.Collections.ArrayList")
	Call objList.Add("Associahedron")
	Call objList.Add("BiscribedDisdyakisDodecahedron")
	Call objList.Add("BiscribedDisdyakisTriacontahedron")
	Call objList.Add("BiscribedDualSnubTruncatedIcosahedron")
	Call objList.Add("BiscribedDualSnubTruncatedOctahedron")
	Call objList.Add("BiscribedHexpropelloCube")
	Call objList.Add("BiscribedHexpropelloDodecahedron")
	Call objList.Add("BiscribedOrthokisPropelloCube")
	Call objList.Add("BiscribedOrthokisPropelloDodecahedron")
	Call objList.Add("BiscribedOrthotruncatedPropelloIcosahedron")
	Call objList.Add("BiscribedOrthotruncatedPropelloOctahedron")
	Call objList.Add("BiscribedPentagonalHexecontahedron")
	Call objList.Add("BiscribedPentagonalIcositetrahedron")
	Call objList.Add("BiscribedPentakisDodecahedron")
	Call objList.Add("BiscribedPentakisSnubDodecahedron")
	Call objList.Add("BiscribedPropelloCube")
	Call objList.Add("BiscribedPropelloDisdyakisDodecahedron")
	Call objList.Add("BiscribedPropelloDisdyakisTriacontahedron")
	Call objList.Add("BiscribedPropelloDodecahedron")
	Call objList.Add("BiscribedPropelloIcosahedron")
	Call objList.Add("BiscribedPropelloOctahedron")
	Call objList.Add("BiscribedPropelloPentagonalIcositetrahedron")
	Call objList.Add("BiscribedPropelloPentakisDodecahedron")
	Call objList.Add("BiscribedPropelloSnubCube")
	Call objList.Add("BiscribedPropelloTetrahedron")
	Call objList.Add("BiscribedPropelloTetrakisHexahedron")
	Call objList.Add("BiscribedPropelloTruncatedCuboctahedron")
	Call objList.Add("BiscribedPropelloTruncatedIcosahedron")
	Call objList.Add("BiscribedPropelloTruncatedIcosidodecahedron")
	Call objList.Add("BiscribedPropelloTruncatedOctahedron")
	Call objList.Add("BiscribedSnubCube")
	Call objList.Add("BiscribedSnubDodecahedron")
	Call objList.Add("BiscribedSnubTruncatedIcosahedron")
	Call objList.Add("BiscribedSnubTruncatedOctahedron")
	Call objList.Add("BiscribedTetrakisHexahedron")
	Call objList.Add("BiscribedTetrakisSnubCube")
	Call objList.Add("BiscribedTruncatedCuboctahedron")
	Call objList.Add("BiscribedTruncatedIcosahedron")
	Call objList.Add("BiscribedTruncatedIcosidodecahedron")
	Call objList.Add("BiscribedTruncatedOctahedron")
	Call objList.Add("BisymmetricHendecahedron")
	Call objList.Add("CanonicalJoinedTruncatedIcosahedron")
	Call objList.Add("ChamferedCube")
	Call objList.Add("ChamferedDodecahedron")
	Call objList.Add("ChamferedIcosahedron")
	Call objList.Add("ChamferedOctahedron")
	Call objList.Add("ChamferedTetrahedron")
	Call objList.Add("ChamferedTruncatedIcosahedron")
	Call objList.Add("ConcaveDodecahedron")
	Call objList.Add("Cube")
	Call objList.Add("CubeOctahedronCompound")
	Call objList.Add("CubeOctahedronToroid")
	Call objList.Add("CubitruncatedCuboctahedron")
	Call objList.Add("Cuboctahedron")
	Call objList.Add("Cubohemioctahedron")
	Call objList.Add("DecagonalDipyramid")
	Call objList.Add("DecagonalPrism")
	Call objList.Add("DecagonalPyramid")
	Call objList.Add("DeltoidalHexecontahedron")
	Call objList.Add("DeltoidalIcositetrahedron")
	Call objList.Add("DisdyakisDodecahedron")
	Call objList.Add("DisdyakisTriacontahedron")
	Call objList.Add("DitrigonalDodecadodecahedron")
	Call objList.Add("Dodecadodecahedron")
	Call objList.Add("Dodecahedron")
	Call objList.Add("DodecahedronIcosahedronCompound")
	Call objList.Add("DualGeodesicIcosahedron1")
	Call objList.Add("DualGeodesicIcosahedron10")
	Call objList.Add("DualGeodesicIcosahedron11")
	Call objList.Add("DualGeodesicIcosahedron12")
	Call objList.Add("DualGeodesicIcosahedron13")
	Call objList.Add("DualGeodesicIcosahedron14")
	Call objList.Add("DualGeodesicIcosahedron15")
	Call objList.Add("DualGeodesicIcosahedron16")
	Call objList.Add("DualGeodesicIcosahedron17")
	Call objList.Add("DualGeodesicIcosahedron18")
	Call objList.Add("DualGeodesicIcosahedron19")
	Call objList.Add("DualGeodesicIcosahedron2")
	Call objList.Add("DualGeodesicIcosahedron20")
	Call objList.Add("DualGeodesicIcosahedron21")
	Call objList.Add("DualGeodesicIcosahedron22")
	Call objList.Add("DualGeodesicIcosahedron23")
	Call objList.Add("DualGeodesicIcosahedron24")
	Call objList.Add("DualGeodesicIcosahedron25")
	Call objList.Add("DualGeodesicIcosahedron3")
	Call objList.Add("DualGeodesicIcosahedron4")
	Call objList.Add("DualGeodesicIcosahedron5")
	Call objList.Add("DualGeodesicIcosahedron6")
	Call objList.Add("DualGeodesicIcosahedron7")
	Call objList.Add("DualGeodesicIcosahedron8")
	Call objList.Add("DualGeodesicIcosahedron9")
	Call objList.Add("DualSnubHexpropelloDodecahedron")
	Call objList.Add("DualSnubTruncatedIcosahedron")
	Call objList.Add("DualSnubTruncatedOctahedron")
	Call objList.Add("DurerSolid")
	Call objList.Add("ElongatedBisymmetricHendecahedron")
	Call objList.Add("ElongatedSphenoidHendecahedron")
	Call objList.Add("ElongatedSquareDipyramid")
	Call objList.Add("ElongatedSquareGyrobicupola")
	Call objList.Add("EnneagonalDipyramid")
	Call objList.Add("EnneagonalPrism")
	Call objList.Add("EnneagonalPyramid")
	Call objList.Add("EscherSolid")
	Call objList.Add("ExpandedJoinedHexpropelloDodecahedron")
	Call objList.Add("ExpandedJoinedTruncatedPentakisDodecahedron")
	Call objList.Add("ExpandedPropelloTruncatedIcosahedron")
	Call objList.Add("GeodesicCube1")
	Call objList.Add("GeodesicCube10")
	Call objList.Add("GeodesicCube11")
	Call objList.Add("GeodesicCube12")
	Call objList.Add("GeodesicCube13")
	Call objList.Add("GeodesicCube14")
	Call objList.Add("GeodesicCube15")
	Call objList.Add("GeodesicCube2")
	Call objList.Add("GeodesicCube3")
	Call objList.Add("GeodesicCube4")
	Call objList.Add("GeodesicCube5")
	Call objList.Add("GeodesicCube6")
	Call objList.Add("GeodesicCube7")
	Call objList.Add("GeodesicCube8")
	Call objList.Add("GeodesicCube9")
	Call objList.Add("GeodesicIcosahedron1")
	Call objList.Add("GeodesicIcosahedron10")
	Call objList.Add("GeodesicIcosahedron11")
	Call objList.Add("GeodesicIcosahedron12")
	Call objList.Add("GeodesicIcosahedron13")
	Call objList.Add("GeodesicIcosahedron14")
	Call objList.Add("GeodesicIcosahedron15")
	Call objList.Add("GeodesicIcosahedron16")
	Call objList.Add("GeodesicIcosahedron17")
	Call objList.Add("GeodesicIcosahedron18")
	Call objList.Add("GeodesicIcosahedron19")
	Call objList.Add("GeodesicIcosahedron2")
	Call objList.Add("GeodesicIcosahedron20")
	Call objList.Add("GeodesicIcosahedron21")
	Call objList.Add("GeodesicIcosahedron22")
	Call objList.Add("GeodesicIcosahedron23")
	Call objList.Add("GeodesicIcosahedron24")
	Call objList.Add("GeodesicIcosahedron25")
	Call objList.Add("GeodesicIcosahedron3")
	Call objList.Add("GeodesicIcosahedron4")
	Call objList.Add("GeodesicIcosahedron5")
	Call objList.Add("GeodesicIcosahedron6")
	Call objList.Add("GeodesicIcosahedron7")
	Call objList.Add("GeodesicIcosahedron8")
	Call objList.Add("GeodesicIcosahedron9")
	Call objList.Add("GreatCubicuboctahedron")
	Call objList.Add("GreatDeltoidalHexecontahedron")
	Call objList.Add("GreatDeltoidalIcositetrahedron")
	Call objList.Add("GreatDirhombicosidodecahedron")
	Call objList.Add("GreatDisdyakisDodecahedron")
	Call objList.Add("GreatDisdyakisTriacontahedron")
	Call objList.Add("GreatDitrigonalDodecacronicHexecontahedron")
	Call objList.Add("GreatDitrigonalDodecicosidodecahedron")
	Call objList.Add("GreatDitrigonalIcosidodecahedron")
	Call objList.Add("GreatDodecacronicHexecontahedron")
	Call objList.Add("GreatDodecahedron")
	Call objList.Add("GreatDodecahemicosahedron")
	Call objList.Add("GreatDodecahemidodecahedron")
	Call objList.Add("GreatDodecicosacron")
	Call objList.Add("GreatDodecicosahedron")
	Call objList.Add("GreatDodecicosidodecahedron")
	Call objList.Add("GreatHexacronicIcositetrahedron")
	Call objList.Add("GreatHexagonalHexecontahedron")
	Call objList.Add("GreatIcosacronicHexecontahedron")
	Call objList.Add("GreatIcosahedron")
	Call objList.Add("GreatIcosicosidodecahedron")
	Call objList.Add("GreatIcosidodecahedron")
	Call objList.Add("GreatIcosihemidodecahedron")
	Call objList.Add("GreatInvertedPentagonalHexecontahedron")
	Call objList.Add("GreatInvertedSnubIcosidodecahedron")
	Call objList.Add("GreatPentagonalHexecontahedron")
	Call objList.Add("GreatPentagrammicHexecontahedron")
	Call objList.Add("GreatPentakisDodecahedron")
	Call objList.Add("GreatRetrosnubIcosidodecahedron")
	Call objList.Add("GreatRhombicTriacontahedron")
	Call objList.Add("GreatRhombidodecacron")
	Call objList.Add("GreatRhombidodecahedron")
	Call objList.Add("GreatRhombihexacron")
	Call objList.Add("GreatRhombihexahedron")
	Call objList.Add("GreatSnubDodecicosidodecahedron")
	Call objList.Add("GreatSnubIcosidodecahedron")
	Call objList.Add("GreatStellapentakisDodecahedron")
	Call objList.Add("GreatStellatedDodecahedron")
	Call objList.Add("GreatStellatedTruncatedDodecahedron")
	Call objList.Add("GreatTriakisIcosahedron")
	Call objList.Add("GreatTriakisOctahedron")
	Call objList.Add("GreatTriambicIcosahedron")
	Call objList.Add("GreatTruncatedCuboctahedron")
	Call objList.Add("GreatTruncatedIcosidodecahedron")
	Call objList.Add("GyrateDeltoidalIcositetrahedron")
	Call objList.Add("HendecagonalPyramid")
	Call objList.Add("HeptagonalAntiprism")
	Call objList.Add("HeptagonalDipyramid")
	Call objList.Add("HeptagonalIrisToroid")
	Call objList.Add("HeptagonalPrism")
	Call objList.Add("HeptagonalPyramid")
	Call objList.Add("HeptagonalTrapezohedron")
	Call objList.Add("HeptagrammicAntiprism1")
	Call objList.Add("HeptagrammicAntiprism2")
	Call objList.Add("HeptagrammicConcaveTrapezohedron")
	Call objList.Add("HeptagrammicCrossedAntiprism")
	Call objList.Add("HeptagrammicDipyramid1")
	Call objList.Add("HeptagrammicDipyramid2")
	Call objList.Add("HeptagrammicPrism1")
	Call objList.Add("HeptagrammicPrism2")
	Call objList.Add("HeptagrammicTrapezohedron1")
	Call objList.Add("HeptagrammicTrapezohedron2")
	Call objList.Add("HexagonalAntiprism")
	Call objList.Add("HexagonalAntiprismTrapezohedronToroid")
	Call objList.Add("HexagonalDipyramid")
	Call objList.Add("HexagonalPrism")
	Call objList.Add("HexagonalPyramid")
	Call objList.Add("HexagonalTrapezohedron")
	Call objList.Add("HexagonalTrapezohedronAntiprismToroid")
	Call objList.Add("HexagonalTrapezohedronToroid")
	Call objList.Add("HexpropelloCube")
	Call objList.Add("HexpropelloDodecahedron")
	Call objList.Add("HugelPolyhedron")
	Call objList.Add("Icosahedron")
	Call objList.Add("Icosidodecadodecahedron")
	Call objList.Add("Icosidodecahedron")
	Call objList.Add("IcositruncatedDodecadodecahedron")
	Call objList.Add("InvertedSnubDodecadodecahedron")
	Call objList.Add("IsohedralToroid")
	Call objList.Add("JessenOrthogonalIcosahedron")
	Call objList.Add("JoinedCuboctahedron")
	Call objList.Add("JoinedIcosidodecahedron")
	Call objList.Add("JoinedRhombicosidodecahedron")
	Call objList.Add("JoinedRhombicuboctahedron")
	Call objList.Add("JoinedSnubCube")
	Call objList.Add("JoinedSnubDodecahedron")
	Call objList.Add("JoinedTruncatedCube")
	Call objList.Add("JoinedTruncatedCuboctahedron")
	Call objList.Add("JoinedTruncatedDodecahedron")
	Call objList.Add("JoinedTruncatedIcosahedron")
	Call objList.Add("JoinedTruncatedIcosidodecahedron")
	Call objList.Add("JoinedTruncatedOctahedron")
	Call objList.Add("JoinedTruncatedTetrahedron")
	Call objList.Add("MedialDeltoidalHexecontahedron")
	Call objList.Add("MedialDisdyakisTriacontahedron")
	Call objList.Add("MedialHexagonalHexecontahedron")
	Call objList.Add("MedialIcosacronicHexecontahedron")
	Call objList.Add("MedialInvertedPentagonalHexecontahedron")
	Call objList.Add("MedialPentagonalHexecontahedron")
	Call objList.Add("MedialRhombicTriacontahedron")
	Call objList.Add("MedialTriambicIcosahedron")
	Call objList.Add("OctagonalAntiprism")
	Call objList.Add("OctagonalDipyramid")
	Call objList.Add("OctagonalIrisToroid")
	Call objList.Add("OctagonalPrism")
	Call objList.Add("OctagonalPyramid")
	Call objList.Add("OctagonalTrapezohedron")
	Call objList.Add("OctagrammicAntiprism")
	Call objList.Add("OctagrammicConcaveTrapezohedron")
	Call objList.Add("OctagrammicCrossedAntiprism")
	Call objList.Add("OctagrammicDipyramid")
	Call objList.Add("OctagrammicPrism")
	Call objList.Add("OctagrammicTrapezohedron")
	Call objList.Add("Octahedron")
	Call objList.Add("Octahemioctahedron")
	Call objList.Add("OrthokisPropelloCube")
	Call objList.Add("OrthokisPropelloDodecahedron")
	Call objList.Add("OrthotruncatedPropelloIcosahedron")
	Call objList.Add("OrthotruncatedPropelloOctahedron")
	Call objList.Add("PentagonalAntiprism")
	Call objList.Add("PentagonalAntiprismTrapezohedronToroid")
	Call objList.Add("PentagonalBifrustum")
	Call objList.Add("PentagonalDipyramid")
	Call objList.Add("PentagonalHexecontahedron")
	Call objList.Add("PentagonalIcositetrahedron")
	Call objList.Add("PentagonalPrism")
	Call objList.Add("PentagonalPyramid")
	Call objList.Add("PentagonalTrapezohedron")
	Call objList.Add("PentagonalTrapezohedronAntiprismToroid")
	Call objList.Add("PentagonalTrapezohedronToroid")
	Call objList.Add("PentagonPolyhedron")
	Call objList.Add("PentagrammicAntiprism")
	Call objList.Add("PentagrammicConcaveTrapezohedron")
	Call objList.Add("PentagrammicCrossedAntiprism")
	Call objList.Add("PentagrammicDipyramid")
	Call objList.Add("PentagrammicPrism")
	Call objList.Add("PentagrammicTrapezohedron")
	Call objList.Add("PentakisDodecahedron")
	Call objList.Add("PentakisIcosidodecahedron")
	Call objList.Add("PentakisSnubDodecahedron")
	Call objList.Add("PropelloCube")
	Call objList.Add("PropelloDisdyakisDodecahedron")
	Call objList.Add("PropelloDisdyakisTriacontahedron")
	Call objList.Add("PropelloDodecahedron")
	Call objList.Add("PropelloIcosahedron")
	Call objList.Add("PropelloOctahedron")
	Call objList.Add("PropelloPentagonaIcositetrahedron")
	Call objList.Add("PropelloPentakisDodecahedron")
	Call objList.Add("PropelloSnubCube")
	Call objList.Add("PropelloTetrahedron")
	Call objList.Add("PropelloTetrakisHexahedron")
	Call objList.Add("PropelloTruncatedCuboctahedron")
	Call objList.Add("PropelloTruncatedIcosahedron")
	Call objList.Add("PropelloTruncatedIcosidodecahedron")
	Call objList.Add("PropelloTruncatedOctahedron")
	Call objList.Add("RectifiedTruncatedIcosahedron")
	Call objList.Add("RegularToroid")
	Call objList.Add("RhombicDodecahedron")
	Call objList.Add("RhombicDodecahemioctahedron")
	Call objList.Add("RhombicEnneacontahedron")
	Call objList.Add("RhombicIcosahedron")
	Call objList.Add("Rhombicosacron")
	Call objList.Add("Rhombicosahedron")
	Call objList.Add("Rhombicosidodecahedron")
	Call objList.Add("RhombicTriacontahedron")
	Call objList.Add("Rhombicuboctahedron")
	Call objList.Add("Rhombidodecadodecahedron")
	Call objList.Add("SchonhardtPolyhedron")
	Call objList.Add("SelfDualIcosioctahedron1")
	Call objList.Add("SelfDualIcosioctahedron2")
	Call objList.Add("SelfDualIcosioctahedron3")
	Call objList.Add("SelfDualIcosioctahedron4")
	Call objList.Add("SelfDualTetracontahedron1")
	Call objList.Add("SelfDualTetracontahedron2")
	Call objList.Add("SelfDualTetracontahedron3")
	Call objList.Add("SelfDualTetracontahedron4")
	Call objList.Add("SelfDualTetracontahedron5")
	Call objList.Add("SelfDualTetracontahedron6")
	Call objList.Add("SmallCubicuboctahedron")
	Call objList.Add("SmallDitrigonalDodecacronicHexecontahedron")
	Call objList.Add("SmallDitrigonalDodecicosidodecahedron")
	Call objList.Add("SmallDitrigonalIcosidodecahedron")
	Call objList.Add("SmallDodecacronicHexecontahedron")
	Call objList.Add("SmallDodecahemicosahedron")
	Call objList.Add("SmallDodecahemidodecahedron")
	Call objList.Add("SmallDodecicosacron")
	Call objList.Add("SmallDodecicosahedron")
	Call objList.Add("SmallDodecicosidodecahedron")
	Call objList.Add("SmallHexacronicIcositetrahedron")
	Call objList.Add("SmallHexagonalHexecontahedron")
	Call objList.Add("SmallHexagrammicHexecontahedron")
	Call objList.Add("SmallIcosacronicHexecontahedron")
	Call objList.Add("SmallIcosicosidodecahedron")
	Call objList.Add("SmallIcosihemidodecahedron")
	Call objList.Add("SmallRetrosnubIcosicosidodecahedron")
	Call objList.Add("SmallRhombidodecacron")
	Call objList.Add("SmallRhombidodecahedron")
	Call objList.Add("SmallRhombihexacron")
	Call objList.Add("SmallRhombihexahedron")
	Call objList.Add("SmallSnubIcosicosidodecahedron")
	Call objList.Add("SmallStellapentakisDodecahedron")
	Call objList.Add("SmallStellatedDodecahedron")
	Call objList.Add("SmallStellatedTruncatedDodecahedron")
	Call objList.Add("SmallTriambicIcosahedron")
	Call objList.Add("SnubCube")
	Call objList.Add("SnubDodecadodecahedron")
	Call objList.Add("SnubDodecahedron")
	Call objList.Add("SnubHexpropelloDodecahedron")
	Call objList.Add("SnubIcosidodecadodecahedron")
	Call objList.Add("SnubTruncatedIcosahedron")
	Call objList.Add("SnubTruncatedOctahedron")
	Call objList.Add("SphenoidHendecahedron")
	Call objList.Add("SquareAntiprism")
	Call objList.Add("SquareAntiprismTrapezohedronToroid")
	Call objList.Add("SquareBifrustum")
	Call objList.Add("SquareDipyramid")
	Call objList.Add("SquarePrism")
	Call objList.Add("SquarePyramid")
	Call objList.Add("StellaOctangula")
	Call objList.Add("StellatedTruncatedHexahedron")
	Call objList.Add("StewartG3")
	Call objList.Add("TetradyakisHexahedron")
	Call objList.Add("TetragonalTrapezohedron")
	Call objList.Add("TetragonalTrapezohedronAntiprismToroid")
	Call objList.Add("TetragonalTrapezohedronToroid")
	Call objList.Add("Tetrahedron")
	Call objList.Add("Tetrahemihexahedron")
	Call objList.Add("TetrakisCuboctahedron")
	'Call objList.Add("TetrakisHexahedron")
	Call objList.Add("TetrakisSnubCube")
	Call objList.Add("TriakisIcosahedron")
	Call objList.Add("TriakisOctahedron")
	Call objList.Add("TriakisTetrahedron")
	Call objList.Add("TriangularAntiprism")
	Call objList.Add("TriangularBifrustum")
	Call objList.Add("TriangularDipyramid")
	Call objList.Add("TriangularPrism")
	Call objList.Add("TridyakisIcosahedron")
	Call objList.Add("TrigonalTrapezohedron")
	Call objList.Add("TruncatedCube")
	Call objList.Add("TruncatedCuboctahedron")
	Call objList.Add("TruncatedDeltoidalHexecontahedron")
	Call objList.Add("TruncatedDeltoidalIcositetrahedron")
	Call objList.Add("TruncatedDisdyakisDodecahedron")
	Call objList.Add("TruncatedDisdyakisTriacontahedron")
	Call objList.Add("TruncatedDodecadodecahedron")
	Call objList.Add("TruncatedDodecahedron")
	Call objList.Add("TruncatedGreatDodecahedron")
	Call objList.Add("TruncatedGreatIcosahedron")
	Call objList.Add("TruncatedIcosahedron")
	Call objList.Add("TruncatedIcosidodecahedron")
	Call objList.Add("TruncatedJoinedTruncatedTetrahedron")
	Call objList.Add("TruncatedOctahedron")
	Call objList.Add("TruncatedPentakisDodecahedron")
	Call objList.Add("TruncatedTetrahedron")
	Call objList.Add("TruncatedTetrakisHexahedron")
	Call objList.Add("TruncatedTriakisIcosahedron")
	Call objList.Add("TruncatedTriakisOctahedron")
	Call objList.Add("TruncatedTriakisTetrahedron")
	Call objList.Add("UniformGreatRhombicosidodecahedron")
	Call objList.Add("UniformGreatRhombicuboctahedron")
	GetPolyhedraCommands = objList.ToArray()   
End Function
