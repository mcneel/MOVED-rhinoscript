'''''''''''''''''''''''''''''''''''''''''''''''''''''''''''''''''''''''''''''
' RandomOffsetCrv.rvb -- April 2013
' If this code works, it was written by Dale Fugier.
' If not, I don't know who wrote it.
' Works with Rhino 4 and 5.
'''''''''''''''''''''''''''''''''''''''''''''''''''''''''''''''''''''''''''''
Option Explicit

'''''''''''''''''''''''''''''''''''''''''''''''''''''''''''''''''''''''''''''
' Randomly offsets one or more closed, planar curves.
' To control the random offset range, just modify the
' RND_MIN and RND_MAX constant values.
'''''''''''''''''''''''''''''''''''''''''''''''''''''''''''''''''''''''''''''
Sub RandomOffsetCrv
  
  ' Declare contants
  Const RH_CRV = 4
  Const RND_MIN = 1.0 ' minimum random number range
  Const RND_MAX = 5.0 ' maximum random number range
  
  ' Declare variables
  Dim arrCurves, strCurve
  Dim arrDirection, dblDistance
  Dim arrPlane, arrNormal, arrBox

  ' Prompt the user to pick some closed, planar curves
  arrCurves = Rhino.GetObjects("Select closed, planar curves to offset randomly", RH_CRV, True, True)
  If IsNull(arrCurves) Then Exit Sub
    
  ' Turn off screen redrawing (for better performance)    
  Call Rhino.EnableRedraw(False)

  ' Initialize random-number generator
  Randomize

  ' Offset each closed planar curve    
  For Each strCurve In arrCurves

    ' Verify the curve is closed
    If Rhino.IsCurveClosed(strCurve) Then
      
      ' Verify the curve is planar
      If Rhino.IsCurvePlanar(strCurve) Then
        
        ' Calculate a point that is outside of the curve
        arrBox = Rhino.BoundingBox(strCurve)
        arrDirection = Rhino.PointAdd(arrBox(0), Rhino.VectorCreate(arrBox(0), arrBox(2)))
        
        ' Get curve's plane and, thus, normal direction
        arrPlane = Rhino.CurvePlane(strCurve)
        arrNormal = arrPlane(3)
        
        ' Calculate a random offset distance
        dblDistance = Rnd * (RND_MAX - RND_MIN) + RND_MIN

        ' Offset the closed, planar curve
        Call Rhino.OffsetCurve(strCurve, arrDirection, dblDistance, arrNormal, 1)

      End If
      
    End If
    
  Next
  
  ' Turn on screen redrawing
  Call Rhino.EnableRedraw(True)
  
End Sub
